module openconfig-grpc-types {
  yang-version "1";
  namespace "http://openconfig.net/yang/grpc/types";
  prefix "oc-grpct";

  import openconfig-extensions {
    prefix oc-ext;
  }

  organization
    "OpenConfig working group";
  contact
    "www.openconfig.net";

  description
    "This module adds gRPC server type relating to gRPC services running on
    a network device.
    The GRPC_SERVICE identity is used to create an extensible list of services
    that can be instantiated, with a base set defined in this module. New
    services can extend the identity to be included in the list.";

  oc-ext:openconfig-version "0.1.0";
  oc-ext:catalog-organization "openconfig";
  oc-ext:origin "openconfig";

  revision "2024-05-29" {
    description
      "Initial revision.";
    reference "0.1.0";
  }

  identity GRPC_SERVICE {
    description
      "Base identity for a gRPC-based service.";
  }
}
