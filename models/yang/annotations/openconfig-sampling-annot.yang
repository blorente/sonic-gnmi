module openconfig-sampling-annot {

    yang-version "1";

    namespace "http://openconfig.net/yang/annotation/oc-sampling-annot";
    prefix "oc-sampling-annot";

    import openconfig-extensions { prefix oc-ext; }
    import openconfig-sampling { prefix oc-sampling; }
    import openconfig-sampling-sflow { prefix oc-sampling-sflow; }
    import sonic-extensions { prefix sonic-ext; }
    import google-pins-sampling-sflow { prefix google-pins-sampling-sflow; }

    deviation /oc-sampling:sampling/oc-sampling-sflow:sflow {
      deviate add {
        sonic-ext:table-name "SFLOW";
        sonic-ext:db-name "CONFIG_DB";
        sonic-ext:subtree-transformer "sflow_xfmr";
      }
    }

    deviation /oc-sampling:sampling/oc-sampling-sflow:sflow/oc-sampling-sflow:collectors {
      deviate add {
        sonic-ext:table-name "SFLOW_COLLECTOR";
        sonic-ext:subtree-transformer "sflow_collector_xfmr";
      }
    }

    deviation /oc-sampling:sampling/oc-sampling-sflow:sflow/oc-sampling-sflow:interfaces {
      deviate add {
        sonic-ext:table-name "SFLOW_SESSION";
        sonic-ext:subtree-transformer "sflow_interface_xfmr";
      }
    }
}
