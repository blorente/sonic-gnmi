module openconfig-optical-switch-annot {
    yang-version "1";

    namespace "http://openconfig.net/yang/annotation/openconfig-optical-swtich-annot";
    prefix "oc-opt-sw-annot";

    import sonic-extensions { prefix sonic-ext; }
    import openconfig-optical-switch { prefix oc-opt-sw; }

    // Ports
    deviation /oc-opt-sw:optical-switch/oc-opt-sw:ports/oc-opt-sw:port {
        deviate add {
            sonic-ext:db-name "CONFIG_DB";
            sonic-ext:table-name "OCS_PORTS";
        }
    }

    deviation /oc-opt-sw:optical-switch/oc-opt-sw:ports/oc-opt-sw:port/oc-opt-sw:state {
        deviate add {
            sonic-ext:db-name "STATE_DB";
        }
    }

    // Port Connections
    deviation /oc-opt-sw:optical-switch/oc-opt-sw:port-connections/oc-opt-sw:port-connection {
        deviate add {
            sonic-ext:db-name "CONFIG_DB";
            sonic-ext:table-name "OCS_XCONNECTS";
        }
    }

    deviation /oc-opt-sw:optical-switch/oc-opt-sw:port-connections/oc-opt-sw:port-connection/oc-opt-sw:state {
        deviate add {
            sonic-ext:db-name "STATE_DB";
            sonic-ext:table-name "OCS_XCONNECTS";
        }
    }

    // Switch Topology
    deviation /oc-opt-sw:optical-switch/oc-opt-sw:optical-switch-topology {
        deviate add {
            sonic-ext:db-name "STATE_DB";
            sonic-ext:table-name "OCS_TOPOLOGY";
            sonic-ext:key-name "global_topology";
        }
    }

    // Port Statuses
    deviation /oc-opt-sw:optical-switch/oc-opt-sw:port-statuses/oc-opt-sw:port-status {
        deviate add {
            sonic-ext:db-name "STATE_DB";
            sonic-ext:table-name "OCS_PORT_STATUSES";
        }
    }

    deviation /oc-opt-sw:optical-switch/oc-opt-sw:port-statuses/oc-opt-sw:port-status/oc-opt-sw:state {
        deviate add {
            sonic-ext:db-name "STATE_DB";
            sonic-ext:table-name "OCS_PORT_STATUSES";
        }
    }

    // Port Connection Recovery
    deviation /oc-opt-sw:optical-switch/oc-opt-sw:port-connection-recovery/oc-opt-sw:config {
        deviate add {
            sonic-ext:db-name "CONFIG_DB";
            sonic-ext:table-name "OCS_XCONNECT_RECOVERY";
            sonic-ext:key-name "global_xconnect_recovery";
        }
    }

    deviation /oc-opt-sw:optical-switch/oc-opt-sw:port-connection-recovery/oc-opt-sw:state {
        deviate add {
            sonic-ext:db-name "STATE_DB";
            sonic-ext:table-name "OCS_XCONNECT_RECOVERY";
            sonic-ext:key-name "global_xconnect_recovery";
        }
    }
}
