module openconfig-optical-switch-deviation {

    yang-version "1";

    // namespace
    namespace "http://openconfig.net/yang/optical-switch/deviation/extension";

    prefix "oc-opt-sw-dev";

    // import some basic types
    import openconfig-extensions { prefix oc-ext; }
    import openconfig-optical-switch { prefix oc-opt-sw; }

    organization
      "SONiC";

    contact
      "SONiC";

    description
      "This module describes a YANG model for openconfig-system deviations.";

    oc-ext:openconfig-version "0.1.0";

    revision "2024-07-15" {
      description
        "Add Yang deviations for unsupported attributes.";
      reference "0.1.0";
    }

    // Unsupported paths
    deviation /oc-opt-sw:optical-switch/oc-opt-sw:port-metadatas {
        deviate not-supported;
    }
    deviation /oc-opt-sw:optical-switch/oc-opt-sw:optical-attenuations {
        deviate not-supported;
    }
    deviation /oc-opt-sw:optical-switch/oc-opt-sw:port-optical-power-measurements {
        deviate not-supported;
    }
    deviation /oc-opt-sw:optical-switch/oc-opt-sw:port-blockings {
        deviate not-supported;
    }


}
