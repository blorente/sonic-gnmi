module openconfig-pins-platform-port {

  yang-version "1";

  // namespace
  namespace "http://openconfig.net/yang/pins-platform-port";

  prefix "pins-platform-port";

  // import some basic types
  import openconfig-extensions { prefix oc-ext; }
  import openconfig-platform { prefix oc-platform; }

  // meta
  organization
    "OpenConfig PINS Working Group";

  contact
    "www.openconfig.net";

  description
    "This module defines schema extensions to the
    OpenConfig port model for the PINS switch profile.";

  oc-ext:openconfig-version "0.1.0";

  revision 2020-04-09 {
    description
      "Initial version.";
    reference "0.1.0";
  }

  // extension statements

  // feature statements

  // identity statements

  // typedef statements

  // grouping statements

  grouping pins-port-config {
    description
      "Configuration data for switch port components";

    leaf port-id {
      type uint32;
      description
        "A numeric identifier assigned by the SDN management
        system for a physical port.  This is used for example
        to create an association between the port and the node
        that manages it.";
    }
  }

  grouping pins-port-state {
    description
      "Operational state data for vendor-agnostic switch port
      components";
  }

  // data definition statements

  // augment statements
  augment "/oc-platform:components/oc-platform:component/" +
          "oc-platform:port/oc-platform:config" {
    description
      "Configuration data for vendor-agnostic switch port components";

    uses pins-port-config;
  }

  // augment statements
  augment "/oc-platform:components/oc-platform:component/" +
          "oc-platform:port/oc-platform:state" {
    description
      "Operational state data for vendor-agnostic switch port components";

    uses pins-port-config;
    uses pins-port-state;
  }

  // rpc statements

  // notification statements

}
