module google-pins-lacp {
  yang-version "1";

  // namespace
  namespace "http://openconfig.net/yang/google/lacp";
  prefix "google-pins-lacp";

  // import some basic types
  import openconfig-extensions { prefix oc-ext; }
  import openconfig-lacp { prefix oc-lacp; }

  // meta
  organization
      "Google Open Config Working Group";

  contact
      "openconfig-dev@google.com";

  description
    "Google Specific extensions to OpenConfig LACP model.";

  oc-ext:openconfig-version "0.2.0";

  revision 2023-02-21 {
    description
      "Adding augments for enabling host signaling.";
    reference "0.2.0";
  }

  revision 2021-11-06 {
    description
      "Adding augments for LACP key.";
    reference "0.1.0";
  }

  // grouping statements
  grouping google-pins-lacp-interface-config {
    description
      "Google specific augments for LACP interface config.";

    leaf lacp-key {
      type uint16;
      description
        "All the member ports of the aggregate interface will use the same LACP
        key configured on the Aggregate interface to establish the LAG.";
    }
  }

  grouping google-pins-lacp-config {
    description
      "Google specific augments for LACP config.";

    leaf enable-host-signaling {
      type boolean;
      description
        "Enable the switch feature to honor the system-priority leaf.";
    }
  }

  // augment statements
  augment "/oc-lacp:lacp/oc-lacp:interfaces/oc-lacp:interface/oc-lacp:config" {
    description
      "Adds Google specific configuration to the LACP interface module.";

    uses google-pins-lacp-interface-config;
  }

  augment "/oc-lacp:lacp/oc-lacp:interfaces/oc-lacp:interface/oc-lacp:state" {
    description
      "Adds Google specific status information to the LACP interface module.";

    uses google-pins-lacp-interface-config;
  }

  augment "/oc-lacp:lacp/oc-lacp:config" {
    description
      "Adds Google specific configuration to the LACP module.";

    uses google-pins-lacp-config;
  }

  augment "/oc-lacp:lacp/oc-lacp:state" {
    description
      "Adds Google specific status information to the LACP module.";

    uses google-pins-lacp-config;
  }
}
