module google-pins-sampling-sflow {
    yang-version "1";
    namespace "http://openconfig.net/yang/google/sampling/sflow";
    prefix "google-pins-sampling-sflow";
    import openconfig-extensions { prefix oc-ext; }
    import openconfig-sampling { prefix oc-sampling; }
    import openconfig-sampling-sflow { prefix oc-sflow; }
    organization
      "Google Openconfig Working Group";
    contact
      "openconfig-dev@google.com";
    description
      "Google Specific extensions to OpenConfig sampling/sflow model.";
    oc-ext:openconfig-version "0.1.0";
    revision "2023-06-01" {
        description
            "Initial revision";
        reference "0.1.0";
    }
  grouping sflow-sampling-rate-state {
    description
      "State data for sFlow sample rates";
    leaf actual-ingress-sampling-rate {
      type uint32;
      description
        "Reports the ingress packet sampling rate.  The rate is expressed
        as an integer N, where the actual sampling rate is 1/N
        packets.  An implementation may implement the sampling rate as
        a statistical average, rather than a strict periodic sampling.
        The allowable sampling rate range is generally a property of
        the system, e.g., determined by the capability of the
        hardware.";
    }
  }
  augment "/oc-sampling:sampling/oc-sflow:sflow/" +
   "oc-sflow:interfaces/oc-sflow:interface/oc-sflow:state" {
    description
      "Add augmentation for sFlow state to the openconfig-sampling model.";
    uses sflow-sampling-rate-state;
  }
  // rpc statements
  // notification statements
}
