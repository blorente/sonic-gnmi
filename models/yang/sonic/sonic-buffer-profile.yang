module sonic-buffer-profile {
    namespace "http://github.com/Azure/sonic-buffer-profile";
    prefix bpf;

    organization
        "SONiC";

    contact
        "SONiC";

    description
        "SONIC BUFFER PROFILE";

    revision 2019-05-15 {
        description
            "Initial revision.";
    }


    container sonic-buffer-profile {

        container BUFFER_PROFILE {

            list BUFFER_PROFILE_LIST {
                key "name";

                leaf name {
                    type string;
                }

                leaf static_th {
                    type uint64;
                }

                leaf dynamic_th {
                    type int64;
                }

                leaf size {
                    type uint64;
                }

                leaf pool {
                    type string;
                }

                leaf xon_offset {
                    type uint64;
                }

                leaf xon {
                    type uint64;
                }

                leaf xoff {
                    type uint64;
                }
            }
        }
    }
}
