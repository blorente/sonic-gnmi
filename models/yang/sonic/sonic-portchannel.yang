module sonic-portchannel {
    namespace "http://github.com/Azure/sonic-portchannel";
    prefix spc;

    import ietf-yang-types {
        prefix yang;
    }

    import sonic-common {
        prefix scommon;
    }

    import sonic-extension {
        prefix sonic-ext;
    }

    import sonic-port {
        prefix prt;
    }

    organization
        "SONiC";

    contact
        "SONiC";

    description
        "SONIC PORTCHANNEL";

    revision 2020-07-30 {
        description
            "Add Portchannel description.";
    }

    revision 2019-05-15 {
        description
            "Initial revision.";
    }

    typedef mode {
        type enumeration {
            enum enable;
            enum disable;
        }
    }

    typedef lag-type {
        type enumeration {
            enum LACP;
            enum STATIC;
        }
    }

    container sonic-portchannel {

        container PORTCHANNEL {

            list PORTCHANNEL_LIST {
                key "name";
                sonic-ext:custom-validation ValidatePortChannelCreationDeletion;

                leaf name {
                    type string {
                        pattern "PortChannel([1-9]|[1-9][0-9]|[1-9][0-9][0-9]|[1-9][0-9][0-9][0-9])" {
                            error-message "Invalid PortChannel name pattern";
                            error-app-tag portchannel-name-invalid;
                        }
                    }
                }

                leaf system_id {
                    type yang:mac-address;
                }

                leaf system_priority {
                    type uint16;
                }

                leaf active {
                    type boolean;
                    default false;
                }

                leaf admin_status {
                    type scommon:admin-status;
                    default up;
                }

                leaf alias {
                    type string;
                }

                leaf mtu {
                    type uint32 {
                        range "1312..9216" {
                            error-message "Invalid MTU value";
                            error-app-tag mtu-invalid;
                        }
                    }
                }

                leaf id {
                    type uint32;
                }

                leaf min_links {
                    type uint8 {
                        range "1..255" {
                            error-message "Invalid Min-links value, valid range 1 to 255";
                            error-app-tag min-links-invalid;
                        }
                    }
                }

                leaf lacp_key {
                    type uint16 {
                    }
                }

                leaf lag_type {
                    type lag-type;
                    description
                        "Describes how the LAG is defined and managed; either statically or with LACP";
                }

                leaf fast_rate {
                    type boolean;
                }

                leaf description {
                    type string;
                    description
                        "Decription of the portchannel";
                }

                leaf fallback {
                    type boolean;
                    description
                      "If the fallback is set to true, current LACP interface is
                      able to establish a Link Aggregation (LAG) before it receives
                      LACP PDUs from its peer, and fallback to a single port active
                      after the expiry of the timeout period.";
                }

                leaf-list members{
                    type string;
                    description
                        "List of portchannel's members";
                }
            }
        }

        container PORTCHANNEL_MEMBER {

            list PORTCHANNEL_MEMBER_LIST {
                key "name ifname";

                leaf name {
                    type leafref {
                        path "../../../PORTCHANNEL/PORTCHANNEL_LIST/name";
                    }
                }

                leaf ifname {
                    type leafref {
                        path "/prt:sonic-port/prt:PORT/prt:PORT_LIST/prt:ifname";
                    }
                }
            }
        }

        container LAG_TABLE {
            config false;

            list LAG_TABLE_LIST {
                key "name";

                leaf name {
                    type string;
                }

                leaf admin_status {
                    type scommon:admin-status;
                }

                leaf mtu {
                    type uint32 {
                        range "1312..9216" {
                            error-message "Invalid MTU value";
                            error-app-tag mtu-invalid;
                        }
                    }
                }

                leaf active {
                    type boolean;
                }

                leaf oper_status {
                    type scommon:oper-status;
                }

                leaf speed {
                    type uint64;
                }
            }
        }

        container LAG_MEMBER_TABLE {
            config false;
            list LAG_MEMBER_TABLE_LIST {
                key "name interface";

                leaf name {
                    type leafref {
                        path "../../../LAG_TABLE/LAG_TABLE_LIST/name";
                    }
                }

                leaf interface {
                    type leafref {
                        path "/prt:sonic-port/prt:PORT/prt:PORT_LIST/prt:ifname";
                    }
                }
                leaf status {
                    type string;
                    description
                        "status of the portchannel member";
                }
            }
        }
    }
}
