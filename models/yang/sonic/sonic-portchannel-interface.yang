module sonic-portchannel-interface {
    namespace "http://github.com/Azure/sonic-portchannel-interface";
    prefix spchint;
    yang-version 1.1;

    import sonic-portchannel {
        prefix spc;
    }

    import sonic-common {
        prefix cmn;
    }

    organization
        "SONiC";

    contact
        "SONiC";

    description
        "SONIC PORTCHANNEL INTERFACE";

    revision 2019-07-02 {
        description
            "Initial revision.";
    }


    container sonic-portchannel-interface {

        container PORTCHANNEL_INTERFACE {

            list PORTCHANNEL_INTERFACE_LIST {
                key "pch_name";

                leaf pch_name{
                    type leafref {
                        path "/spc:sonic-portchannel/spc:PORTCHANNEL/spc:PORTCHANNEL_LIST/spc:name";
                    }
                }

                leaf unnumbered_enabled {
                    must "((/cmn:operation/cmn:operation != 'CREATE') and (/cmn:operation/cmn:operation != 'UPDATE')) or " +
						 "not(contains(/sonic-portchannel-interface/PORTCHANNEL_INTERFACE/PORTCHANNEL_INTERFACE_IPADDR_LIST[pch_name=current()/../pch_name]/ip_prefix, '.'))"
					{
						error-message "Cannot configure IP address and IP Unnumbered interface configurations on the same interface";
						error-app-tag pointf-ip-config;
					}
                    type boolean;
                }

            }

        }
    }
}
