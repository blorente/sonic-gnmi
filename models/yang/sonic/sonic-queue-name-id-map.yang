module sonic-queue-name-id-map {
    namespace "http://github.com/Azure/sonic-queue-name-id-map";
    prefix qnim;

    import sonic-extension {
        prefix sonic-ext;
    }

    organization
        "SONiC";

    contact
        "SONiC";

    description
        "SONIC QUEUE_NAME_TO_ID_MAP";

    revision 2023-03-03 {
        description
            "Initial revision.";
    }

    container sonic-queue-name-id-map {

        container QUEUE_NAME_TO_ID_MAP {

            list QUEUE_NAME_TO_ID_MAP_LIST {
                key "name";
                // every key:value pair is mapped to list keys, e.g. "NC1":"7" ==> qname=NC1, qid=7

                leaf name {
                    type string;
                }

                list QUEUE_NAME_TO_ID_MAP { // this is list inside list for storing mapping between two fields
                    key "qname";

                    leaf qname {
                        type string;
                    }

                    leaf qid {
                        type string {
                            pattern "([1-4][0-9]{3}|[1-9][0-9]{2}|[1-9][0-9]|[0-9])";
                        }
                    }
                }

            }
        }
    }
}
