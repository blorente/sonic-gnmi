module sonic-common {
	namespace "http://github.com/Azure/sonic-common";
	prefix cmn;

	organization
		"SONiC";

	contact
		"SONiC";

	description
		"SONIC common definitions";

  revision 2020-08-04 {
    description
      "Added fec-mode type.";
  }

	revision 2019-05-15 {
		description
			"Initial revision.";
	}

	typedef tagging_mode {
		type enumeration {
			enum untagged;
			enum tagged;
			enum priority_tagged;
		}
	}

	typedef admin-status {
		type enumeration {
			enum up;
			enum down;
		}
	}

	typedef oper-status {
		type enumeration {
			enum up;
			enum down;
		}
	}

  typedef comp-oper-status {
    type enumeration {
      enum active;
      enum inactive;
      enum disabled;
    }
  }

  typedef health-indicator {
    type enumeration {
      enum good;
      enum bad;
    }
  }

  typedef mode-enable {
    type enumeration {
      enum enable;
      enum disable;
    }
  }
  typedef duplex-mode {
    type enumeration {
      enum full;
      enum half;
    }
  }
  typedef fec-mode {
    type enumeration {
      enum rs;
      enum rs528;
      enum rs544;
      enum rs544-interleaved;
      enum fc;
      enum none;
      enum default;
    }
  }

  typedef relay-policy-action {
    type enumeration {
      enum discard;
      enum append;
      enum replace;
    }
  }
}
