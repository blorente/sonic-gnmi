module sonic-ntp-server {
    namespace "http://github.com/Azure/sonic-ntp-server";
    prefix sys;
    yang-version 1.1;

    import sonic-extension {
        prefix sonic-ext;
    }

    organization
        "SONiC";

    contact
        "SONiC";

    description
        "Ntp Server";

    revision 2024-12-26 {
        description
            "Initial revision.";
    }

    container sonic-ntp-server {
        container NTP_SERVER {
            list NTP_SERVER_LIST {
                config false;
                key "address";
                leaf address {
                    type string;
                }
                leaf refId {
                    type string;
                }
                leaf stratum {
                    type string;
                }
                leaf peer_type {
                    type string;
                }
                leaf when {
                    type string;
                }
                leaf poll {
                    type string;
                }
                leaf reach {
                    type string;
                }
                leaf delay {
                    type string;
                }
                leaf offset {
                    type string;
                }
                leaf jitter {
                    type string;
                }
            }
        }
    }
}
