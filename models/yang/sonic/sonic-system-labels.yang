module sonic-system-labels {
    namespace "http://github.com/Azure/sonic-system-labels";
    prefix system-labels;
    yang-version 1.1;

    organization
        "SONiC";

    contact
        "SONiC";

    description
        "SONIC Feature labels";

    revision 2020-04-25 {
        description
            "Initial revision.";
    }

    container sonic-system-labels {
        description
          "Container for the feature labels";

        container FEATURE_LABELS {
            description
             "Enclosing container for the list of feature labels";

            list FEATURE_LABELS_LIST {
                key "label";

                leaf label {
                    type string;
                    description
                        "Feature label key";
                }
            }
        }
    }
}
