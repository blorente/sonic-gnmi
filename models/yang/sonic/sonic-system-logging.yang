module sonic-system-logging {
    namespace "http://github.com/Azure/sonic-system-logging";
    prefix ssys;
    yang-version 1.1;

    import ietf-inet-types {
        prefix inet;
    }

    organization
        "SONiC";

    contact
        "SONiC";

    description
        "DB schema for remote syslog server: openconfig-system logging remote-servers";

    revision 2024-07-16 {
        description
            "Initial version.";
    }

    container sonic-system-logging {
        container SYSLOG_SERVER {
            list SYSLOG_SERVER_LIST {
                key "ipaddress";
                description
                  "List of remote log servers";

                max-elements 8;

                leaf ipaddress {
                    type inet:host;
                    description
                      "Remote syslog server's Domain name or IP address (IPv4 or IPv6)";
                }

                leaf host {
                    type inet:host;
                    description
                      "Remote syslog server's Domain name or IP address (IPv4 or IPv6)";
                }

                leaf remote-port {
                    default 514;
                    type inet:port-number;
                }
            }
        }
    }
}
