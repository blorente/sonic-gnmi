module sonic-dscp-tc-map {
    namespace "http://github.com/Azure/sonic-dscp-tc-map";
    prefix dtm;

    import sonic-extension {
        prefix sonic-ext;
    }

    organization
        "SONiC";

    contact
        "SONiC";

    description
        "SONIC DSCP_TO_TC_MAP";

    revision 2019-05-15 {
        description
            "Initial revision.";
    }

    container sonic-dscp-tc-map {	

        container DSCP_TO_TC_MAP {

            list DSCP_TO_TC_MAP_LIST {
                key "name";
                //every key:value pair is mapped to list keys, e.g. "1":"7" ==> dscp=1, tc_num=7

                leaf name {
                    type string {
                        pattern '[a-zA-Z0-9]{1}([-a-zA-Z0-9_]{0,31})';
                        length 1..32;
                    }
                }

                list DSCP_TO_TC_MAP { //this is list inside list for storing mapping between two fields
                    key "dscp";

                    leaf tc_num {
                        type string {
                            pattern "[0-9]?"{
                                error-message "Invalid Traffic Class number";
                                error-app-tag tc-num-invalid;
                            }
                        }
                    }

                    leaf dscp {
                        type string {
                            pattern "[1-9][0-9]?|[0-9]?";
                        }
                    }
                }

            }
        }
    }
}
