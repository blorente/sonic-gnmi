module sonic-loopback {
    namespace "http://github.com/Azure/sonic-loopback";
    prefix sonic-lo;

    import sonic-common {
        prefix scommon;
    }

    organization
        "SONiC";

    contact
        "SONiC";

    description
        "SONIC LOOPBACK";

    revision 2020-07-26 {
            description
                        "Add separate L2 table for Loopback interface";
    }

    container sonic-loopback {

        container LOOPBACK {

            list LOOPBACK_LIST {
                key "name";

                leaf name {
                    type string {
                            pattern "Loopback([0-9]|[1-8][0-9]|9[0-9]|[1-8][0-9]{2}|" +
                                    "9[0-8][0-9]|99[0-9]|[1-8][0-9]{3}|9[0-8][0-9]{2}|" +
                                    "99[0-8][0-9]|999[0-9]|1[0-5][0-9]{3}|16[0-2][0-9]{2}|163[0-7][0-9]|1638[0-3])";
                   }
                }

                leaf description {
                    type string;
                }

                leaf admin_status {
                    type scommon:admin-status;
                    default up;
                }
             }
        }
    }
}
