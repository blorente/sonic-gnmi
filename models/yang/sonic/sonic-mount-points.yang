module sonic-mount-points {
    namespace "http://github.com/Azure/sonic-mount-points";
    prefix sys;
    yang-version 1.1;

    import sonic-extension {
        prefix sonic-ext;
    }

    organization
        "SONiC";

    contact
        "SONiC";

    description
        "Mount Points";

    revision 2024-12-26 {
        description
            "Initial revision.";
    }

    container sonic-mount-points{
        container MOUNT_POINTS {
            list MOUNT_POINTS_LIST {
                config false;
                key "name";
                leaf name {
                    type string;
                }

                leaf filesystem {
                    type string;
                }
                leaf filesystem-type {
                    type string;
                }
                leaf available {
                    type string;
                }
                leaf used {
                    type string;
                }
                leaf size {
                    type string;
                }
            }
        }
    }
}
