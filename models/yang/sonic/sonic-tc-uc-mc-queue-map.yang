module sonic-tc-uc-mc-queue-map {
    namespace "http://github.com/Azure/sonic-tc-uc-mc-queue-map";
    prefix tumqm;

    import sonic-extension {
        prefix sonic-ext;
    }

    organization
        "SONiC";

    contact
        "SONiC";

    description
        "SONIC TC_TO_UC_MC_QUEUE_MAP";

    revision 2023-11-21 {
        description
            "Initial revision.";
    }

    container sonic-tc-uc-mc-queue-map {

        container TC_TO_UC_MC_QUEUE_MAP {

            list TC_TO_UC_MC_QUEUE_MAP_LIST {
                key "name";
                //every key:value pair is mapped to list keys, e.g. "UNICAST:1":"7" ==> tc=1, qindex=7 for unicast

                leaf name {
                    type string {
                        pattern '[a-zA-Z0-9]{1}([-a-zA-Z0-9_]{0,31})';
                        length 1..32;
                    }
                }

                list TC_TO_UC_MC_QUEUE_MAP { //this is list inside list for storing mapping between two fields
                    key "prefix_tc";

                    leaf prefix_tc {
                        type string;
                    }

                    leaf qindex {
                        type string {
                            pattern "([1-4][0-9]{3}|[1-9][0-9]{2}|[1-9][0-9]|[0-9])";
                        }
                    }
                }
            }
        }
    }
}
